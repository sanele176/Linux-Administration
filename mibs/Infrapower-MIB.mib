-- *************************************************************************
-- AUSTIN HUGHES ELECTRONICS LTD INFRAPOWER-MIB
-- *************************************************************************
-- Copyright (c) 2015 Austin Hughes Electronics Ltd.
-- InfraPower is a Trademark of Austin Hughes Electronics Ltd.
--
-- Title: AH InfraPower ATS/PDU MIB
--
-- Version : 4.4.0
--
-- Generated by script: edc
--
-- Input File: InfraPower-MIB.mib
--
-- Last Update: Thursday, February, 20, 2020
--
-- Revision History:
-- *************************************************************************
-- 2020/06/29 - v4.4.0
--      -Added support for 208V-DF-12B, 400V-DF-12B
--      -The SYNTAX of OBJECT-TY 'circuitIndex' is updated to INTEGER (1..12)
--      -The SYNTAX of OBJECT-TY 'circuitBreakerIndex' is updated to INTEGER (1..12)
--      -The SYNTAX of OBJECT-TY 'stdOutletCircuit' is updated to DisplayString (SIZE (2))
--      -The SYNTAX of OBJECT-TY 'c19OutletCircuit' is updated to DisplayString (SIZE (2))
-- 2020/02/20 - v4.2.0
--      -Updated DESCRIPTION for OBJECT-TYPE tHSensorTableEntry,tHSensorType,tHSensorAlarmState,tempSensorValue and tempSensorValueStr.
--      -Updated DESCRIPTION for NOTIFICATION-TYPE tempSensorEventTriggered and sensorConnectionLost.
--		-Added traps circuitLoadEventCleared,sensorConnectionRecovered,tempSensorEventCleared, humiSensorEventCleared, pduConnectionRecovered
--		-Added traps smokeSensorEventTriggered,doorSensorEventTriggered,doorSensorEventCleared,smokeSensorEventCleared
-- 2019/11/25 - v4.1.8
--      -Added oid pduSerialNo DisplayString (SIZE (1..32))

-- 2019/07/01 - v4.1.7
--      -Updated SYNTAX for	pduMainLoadAmp to DisplayString (SIZE (1..3))
--      -Updated SYNTAX for	pduMainActivePower to DisplayString (SIZE (1..7))
--      -Updated SYNTAX for	pduMainApparentPower to DisplayString (SIZE (1..7))
--      -Updated SYNTAX for	pduMainCumulativeEnergy to DisplayString (SIZE (1..8))
--      -Fixed error on SYNTAX of RCMSensorTableEntry to RCMSensorTableEntry (from THSensorTableEntry)
--      -Fixed error on SYNTAX of rCMSensorAlarmThresh to INTEGER
--      -Fixed error on SYNTAX of rCMSensorRisingAlertThresh to INTEGER
--      -Fixed error on SYNTAX of rCMSensorLowAlertThresh to INTEGER
--      -Removed rCMSensorPeakReading, rCMSensorPeakReadingReset and rCMSensorActivation from rCMSensorTableEntry
--      -Added rCMSensors to pduEntry

-- 2019/05/30 - v4.1.6
--      -Updated SYNTAX for	pduMainLoadAmp to DisplayString (SIZE (1..3))
--      -Updated SYNTAX for	pduMainActivePower to DisplayString (SIZE (1..7))
--      -Updated SYNTAX for	pduMainApparentPower to DisplayString (SIZE (1..7))
--      -Updated SYNTAX for	pduMainCumulativeEnergy to DisplayString (SIZE (1..8))
--      -Support PDU with RCM sensor
--      -Added rCMSensors to pduEntry
--      -Added RCM traps (rcmSensorEventTriggered, rcmSensorEventCleared, rcmSensorConnectionLost, rcmSensorConnectionRecovered)

--
-- 2018/07/19 - v4.1.4
--      -Removed OutletTable for all outlets
--
-- 2018/06/21 - v4.1.3
--      -Added OutletTable for all outlets
--
-- 2018/06/05 - v4.0.2
--      -Changed description of atsTotalLoadAmp, atsOverLoadThreshold, infraPowerwebAccessNotificationsGroup
--      -Removed circuitEnergy
--      -Chnaged description of 'circuitActivePower','circuitApparentPower'
--
-- 2018/06/01 - v4.0.1
--      -Changed description of atsInputSwitch
--
-- 2018/05/16 - v4.0.0
--      -Added support for InfraPower ATS.
--		-Added object 'infraPowerATSGroup', 'infraPowerATSNotificationsGroup'
--		-Added object 'atsTraps'
--
-- 2017/12/18 - v3.9.0
--      -Added object 'circuitEnergy','circuitPowerFactor','circuitActivePower','circuitApparentPower'
--
-- 2017/09/29 - v3.8.0
--      -Added object 'circuitCumulativeEnergyReset'
--
-- 2016/11/07 - v3.7.1
--      -Changed MAX-ACCESS of OBJECT-TYPE 'tempSensorLowerAlarmThresh' to read-only.
--      -Changed MAX-ACCESS of OBJECT-TYPE 'humiSensorLowerAlarmThresh' to read-only.
--      -Changed MAX-ACCESS of OBJECT-TYPE 'tHSensorActivation' to read-write.
--
-- 2016/09/22 - v3.6
--      -IMPORTS from SNMPv2-CONF,SNMPv2-TC and SNMPv2-SMI
--      -Added MODULE-IDENTITY, OBJECT-GROUP, NOTIFICATION-GROUP
--      -SMIv2 standard.
--
-- 2016/09/22 - v3.5
--      -The SYNTAX of OBJECT-TYPE 'circuitState' is updated to INTEGER {Normal(0),Alarm(1),RisingAlert(2),LowAlert(3),NotExist(4)}.
--      -The SYNTAX of OBJECT-TYPE 'stdOutletAlarmState' is updated to INTEGER {Normal(0),Alarm(1),RisingAlert(2),LowAlert(3),NotExist(4)}.
--      -The SYNTAX of OBJECT-TYPE 'c19OutletAlarmState' is updated to INTEGER {Normal(0),Alarm(1),RisingAlert(2),LowAlert(3),NotExist(4)}.
--      -Changed object name 'AustinHughes' to 'austinHughes'
--      -Changed object name 'InfraPower' to 'infraPower'
--      -Changed object name 'THSensors' to 'tHSensors'
--      -Added object 'circuitLoadAmpRisingAlertThresh'
--      -changed MAX-ACCESS write-only to MAX-ACCESS read-write for SMIv2 compatible.
--       ('circuitLoadPeakAmpReset','stdOutletPeakAmpReset','stdOutletCumulativeEnergyReset','c19OutletPeakAmpReset','c19OutletCumulativeEnergyReset')
--      -changed IMPORTS (enterprises, OBJECT-TYPE, NOTIFICATION-TYPE FROM SNMPv2-SMI
--
-- 2015/03/20 - v3.0
--      -Added support for InfraPower W3PDU
--      -The SYNTAX of OBJECT-TY 'PpduMainLoadVoltage' is updated to DisplayString (SIZE (4..12))
--      -The SYNTAX of OBJECT-TY 'circuitIndex' is updated to INTEGER (1..6)
--      -The SYNTAX of OBJECT-TY 'circuitBreakerIndex' is updated to INTEGER (1..6)
-- 2014/07/21 - v2.6
--      -Updated description
-- 2014/01/21 - v2.5
--      -Updated description
-- 2014/01/21 - v2.4
--      -Remove imports from INET-ADDRESS-MIB for InetAddressIPv4
--      -Embedded the InetAddressIPv4 TEXTUAL-CONVENTION in this mib
--      -Embedded the DateAndTime TEXTUAL-CONVENTION in this mib
--      -Embedded the DisplayString TEXTUAL-CONVENTION in this mib
--       (no need to load SNMPv2-TC, SNMPv2-TC & DisplayString from external mib files)
-- 2013/07/12 - v2.3
--      -updated description to outlet
-- 2013/05/14 - v2.2
--      -THSensorActivation is changed to read-only.
-- 2013/05/03 - v2.1
--      -added imports to InetAddressIPv4 from INET-ADDRESS-MIB.
-- 2013/04/09 - v2.0
--      -added individaul outlet Alarm, LowAlert threhold, PowerUpSeqDelay setup.
--      -added read-only pdu RealTimeClock OID.
-- 2013/02/07 - v1.2
--      -limited Trap to circuit alarm, breaker status change, th alarm, th disconnection !
--
-- ********************************************************************************************
-- ********************************************************************************************
-- InfraPower-MIB { iso org(3) dod(6) internet(1) private(4)
--    enterprises(1) AustinHughes(34550) }

InfraPower-MIB DEFINITIONS ::= BEGIN
	IMPORTS
		enterprises, OBJECT-TYPE, NOTIFICATION-TYPE, MODULE-IDENTITY, OBJECT-IDENTITY	FROM SNMPv2-SMI
		TEXTUAL-CONVENTION, DisplayString 	FROM SNMPv2-TC
		OBJECT-GROUP, NOTIFICATION-GROUP 	FROM SNMPv2-CONF;
	-- IMPORTS End
	--------------------------------------------------------------------------------
	infraPower MODULE-IDENTITY
	    LAST-UPDATED "201609221226Z"            -- 22 Sep 2016, 12:26
	    ORGANIZATION "www.austin-hughes.com"
	    CONTACT-INFO "      APAC
	                        =========================================================
	                        Austin Hughes Electronics Ltd.
	                        Unit 3608-12, Cable TV Tower,
	                        9 Hoi Shing Road, Tsuen Wan,
	                        Hong Kong
	                        email : support@austin-hughes.com
	                        
	                        China
	                        =========================================================
	                        Austin Hughes Electronics (China) Ltd.
	                        Hexi Road No.2 Jinxia Industrial Area,
	                        Changan Town, Dongguan City
	                        Guangdong Province 523850
	                        China
	                        
	                        Americas
	                        =========================================================
	                        Austin Hughes Solutions Inc.
	                        41320 Boyce Road, Fremont,
	                        CA 94538,
	                        USA
	                        
	                        EMEA
	                        =========================================================
	                        Austin Hughes Europe Ltd.
	                        Unit 1, Chancery Gate Business Centre,
	                        Manor House Avenue,
	                        Southampton, SO15 0AE
	                        United Kingdom
			 "
	    DESCRIPTION  "SNMP MIB file for InfraPower PDU.
			 "
	    REVISION      "201609221226Z"
	    DESCRIPTION
		    " 1) Fixed SYNTAX error for 'circuitState','stdOutletAlarmState','c19OutletAlarmState'
		      2) SMIv2 standard
		    "
	    ::= { enterprises 34550 20 }
	--------------------------------------------------------------------------------
	austinHughes				OBJECT IDENTIFIER ::= { enterprises 34550 }
	ipDongle				OBJECT IDENTIFIER ::= { infraPower 1 }
	pduGroup				OBJECT IDENTIFIER ::= { infraPower 2 }
	infraPowerMIBGroups			OBJECT IDENTIFIER ::= { infraPower 3 }
	atsGroup			OBJECT IDENTIFIER ::= { infraPower 4 }
	--------------------------------------------------------------------------------
	infraPowerIPDongleGroup OBJECT-GROUP
	       OBJECTS { ipdongleModel,
			 ipdongleName,
			 ipdongleLocation,
			 ipdongleMacAddress,
			 ipdongleIpAddressIpv4,
			 ipdongleSubnetIpv4,
			 ipdongleGatewayIpv4 }
	       STATUS  current
	       DESCRIPTION
		       "A collection of objects providing basic instrumentation
		       and control of the ipdongle."
	      ::= { infraPowerMIBGroups 1 }
	infraPowerPDUGroup OBJECT-GROUP
	       OBJECTS { pduIndex,
			 pduModel,
			 pduID,
			 pduSerialNo,
			 pduName,
			 pduLocation,
			 pduGroupNumber,
			 pduMainLoadVoltage,
			 pduMainLoadAmp,
			 pduMainPowerFactor,
			 pduMainActivePower,
			 pduMainApparentPower,
			 pduMainCumulativeEnergy,
			 pduRealTimeClock
			 --circuits,
			 --circuitBreakers,
			 --outlets,
			 --tHSensors 
			 --rCMSensors 
			 }
	       STATUS  current
	       DESCRIPTION
		       "A collection of objects providing basic instrumentation
		       and control of the PDU."
	      ::= { infraPowerMIBGroups 2 }
	infraPowerCircuitGroup OBJECT-GROUP
	       OBJECTS { circuitIndex,
			 circuitRatedAmp,
			 circuitName,
			 circuitState,
			 circuitLoadVoltage,
			 circuitLoadAmp,
			 circuitPowerFactor,
			 circuitActivePower,
			 circuitApparentPower,
			 circuitLoadPeakAmp,
			 circuitCumulativeEnergy,
			 circuitLoadPeakAmpReset,
			 circuitBreakerStateCopy,
			 circuitLoadAmpAlarmThresh,
			 circuitLoadAmpRisingAlertThresh,
			 circuitLoadAmpLowAlertThresh,
			 circuitCumulativeEnergyReset}
	       STATUS  current
	       DESCRIPTION
		       "A collection of objects providing basic instrumentation
		       and control of the circuits."
	      ::= { infraPowerMIBGroups 3 }
	infraPowerCircuitBreakerGroup OBJECT-GROUP
	       OBJECTS { circuitBreakerIndex,
			circuitBreakerRatedAmp,
			circuitBreakerState }
	       STATUS  current
	       DESCRIPTION
		       "A collection of objects providing basic instrumentation
		       and control of the circuit breaks."
	      ::= { infraPowerMIBGroups 4 }
	infraPowerStdOutletGroup OBJECT-GROUP
	       OBJECTS { stdOutletIndex,
			 stdOutletCircuit,
			 stdOutletType,
			 stdOutletName,
			 stdOutletPowerStatus,
			 stdOutletAlarmState,
			 stdOutletLoadAmp,
			 stdOutletEnergy,
			 stdOutletPeakAmp,
			 stdOutletCumulativeEnergy,
			 stdOutletLoadAmpAlarmThresh,
			 stdOutletLoadAmpRAlertThresh,
			 stdOutletLoadAmpLAlertThresh,
			 stdOutletPeakAmpReset,
			 stdOutletCumulativeEnergyReset,
			 stdOutletPowerUpSequenceDelay }
	       STATUS  current
	       DESCRIPTION
		       "A collection of objects providing basic instrumentation
		       and control of the non C19 outlets."
	      ::= { infraPowerMIBGroups 5 }
	infraPowerC19OutletGroup OBJECT-GROUP
	       OBJECTS { c19OutletIndex,
			 c19OutletCircuit,
			 c19OutletType,
			 c19OutletName,
			 c19OutletPowerStatus,
			 c19OutletAlarmState,
			 c19OutletLoadAmp,
			 c19OutletEnergy,
			 c19OutletPeakAmp,
			 c19OutletCumulativeEnergy,
			 c19OutletLoadAmpAlarmThresh,
			 c19OutletLoadAmpRAlertThresh,
			 c19OutletLoadAmpLAlertThresh,
			 c19OutletPeakAmpReset,
			 c19OutletCumulativeEnergyReset,
			 c19OutletPowerUpSequenceDelay }
	       STATUS  current
	       DESCRIPTION
		       "A collection of objects providing basic instrumentation
		       and control of the C19 outlets."
	      ::= { infraPowerMIBGroups 6 }
	infraPowerTHSensorGroup OBJECT-GROUP
	       OBJECTS { tHSensorIndex,
			 tHSensorLocation,
			 tHSensorType,
			 tHSensorConnState,
			 tHSensorAlarmState,
			 tempSensorValue,
			 tempSensorValueStr,
			 tempSensorUpperAlarmThresh,
			 tempSensorLowerAlarmThresh,
			 humiSensorValue,
			 humiSensorValueStr,
			 humiSensorUpperAlarmThresh,
			 humiSensorLowerAlarmThresh,
			 tHSensorActivation }
	       STATUS  current
	       DESCRIPTION
		       "A collection of objects providing basic instrumentation
		       and control of the TH Sensor."
	      ::= { infraPowerMIBGroups 7 }
		  
	   infraPowerNotificationsGroup NOTIFICATION-GROUP
		   NOTIFICATIONS { circuitLoadEventTriggered, circuitBreakerTripped, circuitBreakerRecovered, sensorConnectionLost, tempSensorEventTriggered, humiSensorEventTriggered, pduConnectionLost, circuitLoadEventCleared,sensorConnectionRecovered,tempSensorEventCleared, humiSensorEventCleared, pduConnectionRecovered, rcmSensorEventTriggered, rcmSensorEventCleared, rcmSensorConnectionLost, rcmSensorConnectionRecovered,smokeSensorEventTriggered,doorSensorEventTriggered,doorSensorEventCleared,smokeSensorEventCleared,feedConnectionLost,feedConnectionRecovered }
	       --NOTIFICATIONS { circuitLoadEventTriggered, circuitBreakerTripped, circuitBreakerRecovered, sensorConnectionLost, tempSensorEventTriggered, humiSensorEventTriggered, pduConnectionLost, rcmSensorEventTriggered, rcmSensorEventCleared, rcmSensorConnectionLost, rcmSensorConnectionRecovered }
	       STATUS        current
	       DESCRIPTION
		       "The  notifications which InfraPower agent is required to
		       implement."
	      ::= { infraPowerMIBGroups 9 }
		infraPowerwebAccessNotificationsGroup NOTIFICATION-GROUP
			   NOTIFICATIONS { webLogin }
			   STATUS        current
			   DESCRIPTION
				   "The  notifications which InfraPower agent is required to
		       implement."
			  ::= { infraPowerMIBGroups 10 }
		infraPowerwebAccessGroup OBJECT-GROUP
			   OBJECTS { objectDateTime,
				 userName,
				 webAccessIpAddress }
			   STATUS  current
			   DESCRIPTION
				   "A collection of objects providing basic instrumentation
				   and web login trap of the ipdongle."
			  ::= { infraPowerMIBGroups 11 }
	   infraPowerATSNotificationsGroup NOTIFICATION-GROUP
	       NOTIFICATIONS {atsOverLoadEventTriggered, atsOverLoadEventCleared, atsPrimaryFeedOfflineEventTriggered, atsPrimaryFeedOfflineEventCleared, atsSecondaryFeedOfflineEventTriggered, atsSecondaryFeedOfflineEventCleared, atsInputSwitchEventTriggered, atsOnFailAutoSwitchFeedEventTriggered, atsConnectionLost, atsConnectionRecovered }
	       STATUS        current
	       DESCRIPTION
		       "The ATS notifications which InfraPower agent is required to
		       implement."
	      ::= { infraPowerMIBGroups 12 }
		infraPowerATSGroup OBJECT-GROUP
	       OBJECTS { atsIndex,
			 atsModel,
			 atsID,
			 atsName,
			 atsLocation,
			 atsInputSwitch,
			 atsFeedPrimaryStatus,
			 atsFeedSecondaryStatus,
			 atsOutputFromFeed,
			 atsTotalLoadAmp,
			 atsOverLoadThreshold,
			 atsOverLoadStage,
			 atsConnection }
	       STATUS  current
	       DESCRIPTION
		       "A collection of objects providing basic instrumentation
		       and control of the ATS."
	      ::= { infraPowerMIBGroups 8 }
		  
	--------------------------------------------------------------------------------
	-- textual conventions
	-- InetAddressIPv4 is extrated from INET-ADDRESS-MIB
	InetAddressIPv4 ::= TEXTUAL-CONVENTION
	    DISPLAY-HINT "1d.1d.1d.1d"
	    STATUS       current
	    DESCRIPTION
		"Represents an IPv4 network address:


		   Octets   Contents         Encoding
		    1-4     IPv4 address     network-byte order

		 The corresponding InetAddressType value is ipv4(1).

		 This textual convention SHOULD NOT be used directly in object
		 definitions, as it restricts addresses to a specific format.
		 However, if it is used, it MAY be used either on its own or in
		 conjunction with InetAddressType, as a pair."
	    SYNTAX       OCTET STRING (SIZE (4))
	--------------------------------------------------------------------------------

	infraPowerRCMSensorGroup OBJECT-GROUP
	       OBJECTS { rCMSensorIndex,
			 rCMSensorLocation,
			 rCMSensorReading,
			 rCMSensorConnState,
			 rCMSensorAlarmState,
			 rCMSensorAlarmThresh,
			 rCMSensorRisingAlertThresh,
			 rCMSensorLowAlertThresh }
	       STATUS  current
	       DESCRIPTION
		       "A collection of objects providing basic instrumentation
		       and control of the RCM Sensor."
	      ::= { infraPowerMIBGroups 13 }
		  

	--
	--	rCMSensors (Residual Current Monitoring)
	--
	rCMSensors				OBJECT IDENTIFIER ::= { pduEntry 28 }

	rCMSensorTable        OBJECT-TYPE
		SYNTAX      SEQUENCE OF RCMSensorTableEntry
		MAX-ACCESS	not-accessible
		STATUS      current
		DESCRIPTION
			"Table of RCMsensor"
		::= { rCMSensors 1 }

	rCMSensorTableEntry        OBJECT-TYPE
		SYNTAX      RCMSensorTableEntry
		MAX-ACCESS  not-accessible
		STATUS 	    current
		DESCRIPTION
			"Table entries of RCMSensor"
		INDEX   { pduIndex,
					rCMSensorIndex }
		::= { rCMSensorTable 1 }

	RCMSensorTableEntry ::=
		SEQUENCE {
			rCMSensorIndex						INTEGER,
			rCMSensorLocation					DisplayString,
			rCMSensorReading					INTEGER,
			rCMSensorConnState					INTEGER,
			rCMSensorAlarmState					INTEGER,
			rCMSensorAlarmThresh				INTEGER,
			rCMSensorRisingAlertThresh			INTEGER,
			rCMSensorLowAlertThresh				INTEGER
		}
	rCMSensorIndex OBJECT-TYPE
		SYNTAX      INTEGER (1..13)
		MAX-ACCESS  read-only
		STATUS      current
		DESCRIPTION
			"The id of the sensor.
			 (1)=RCM1, (2)=RCM2 .. (13)=RCM13."
		::= { rCMSensorTableEntry 1 }
	rCMSensorLocation OBJECT-TYPE
		SYNTAX      DisplayString (SIZE (0..16))
		MAX-ACCESS  read-write
		STATUS      current
		DESCRIPTION
			"The location descriotion of the sensor.
			 The valid characters are (0 to 9), (a to z), (A to Z), (_), (-) and (.)."
		::= { rCMSensorTableEntry 2 }
	rCMSensorReading OBJECT-TYPE
		SYNTAX      INTEGER (0..9999)
		MAX-ACCESS  read-only
		STATUS      current
		--UNITS "mA"
		--DISPLAY-HINT "d-1"
		DESCRIPTION
			"The leakage current measured in tenth of mA.
			 (0)=0mA, (10)=1mA, (123)=12.3mA, (9999)=999.9mA."
		::= { rCMSensorTableEntry 3 }
	rCMSensorConnState OBJECT-TYPE
		SYNTAX      INTEGER {
				   disconnected    (0),
				   connected       (1)
				}
		MAX-ACCESS  read-only
		STATUS      current
		DESCRIPTION
			"The connection status of this RCM sensor.
			 (0)=disconnected, (1)=connected."
		::= { rCMSensorTableEntry 4 }

	rCMSensorAlarmState OBJECT-TYPE
		SYNTAX      INTEGER {
				   normal      (0),
				   alarm       (1),
				   risingAlert (2)
				}
		MAX-ACCESS  read-only
		STATUS      current
		DESCRIPTION
			"The alarm state of this RCM sensor.
			 (0) = normal, (1) = alarm, (2)=rising alert."
		::= { rCMSensorTableEntry 5 }


	rCMSensorAlarmThresh OBJECT-TYPE
		SYNTAX      INTEGER (0..9999)
		MAX-ACCESS  read-write
		STATUS      current
		--UNITS       "mA"
		--DISPLAY-HINT "d-1"
		DESCRIPTION
			"The leakage current alarm threshold in tenth of mA.
			 (0)=0mA, (10)=1mA, (123)=12.3mA, (9999)=999.9mA."
		::= { rCMSensorTableEntry 6 }
	rCMSensorRisingAlertThresh OBJECT-TYPE
		SYNTAX      INTEGER (0..9999)
		MAX-ACCESS  read-write
		STATUS      current
		--UNITS "mA"
		--DISPLAY-HINT "d-1"
		DESCRIPTION
			"The leakage current rising alert threshold in tenth of mA.
			 (0)=0mA, (10)=1mA, (123)=12.3mA, (9999)=999.9mA."
		::= { rCMSensorTableEntry 7 }
	rCMSensorLowAlertThresh OBJECT-TYPE
		SYNTAX      INTEGER (0..9999)
		MAX-ACCESS  read-write
		STATUS      current
		--UNITS "mA"
		--DISPLAY-HINT "d-1"
		DESCRIPTION
			"The leakage current low alert threshold in tenth of mA.
			 (0)=0mA, (10)=1mA, (123)=12.3mA, (9999)=999.9mA."
		::= { rCMSensorTableEntry 8 }


	--	ipDongleAdmin
	--
	ipDongleAdmin			OBJECT IDENTIFIER ::= { ipDongle 1 }

	ipdongleModel  OBJECT-TYPE
		SYNTAX      DisplayString (SIZE (1..32))
		MAX-ACCESS  read-only
		STATUS      current
		DESCRIPTION
			"The model number of the product."
		::= { ipDongleAdmin 1 }
		--main_conf.AppText
	ipdongleName  OBJECT-TYPE
		SYNTAX      DisplayString (SIZE (1..16))
		MAX-ACCESS  read-write
		STATUS      current
		DESCRIPTION
			"The name of the product.
			 SET: input length = 1 to 16 characters.
			 The valid characters are (0 to 9), (a to z), (A to Z), (_), (-) and (.)."
		::= { ipDongleAdmin 5 }
		--main_conf.DeviceName
	ipdongleLocation  OBJECT-TYPE
		SYNTAX      DisplayString (SIZE (1..16))
		MAX-ACCESS  read-write
		STATUS      current
		DESCRIPTION
			"The location of the product.
			 SET: input length = 1 to 16 characters.
			 The valid characters are (0 to 9), (a to z), (A to Z), (_), (-) and (.)."
		::= { ipDongleAdmin 6 }
		--main_conf.Location
	ipdongleMacAddress  OBJECT-TYPE
		SYNTAX      OCTET STRING (SIZE (0..255))
		MAX-ACCESS  read-only
		STATUS      current
		DESCRIPTION
			"The MAC address of the products"
		::= { ipDongleAdmin 8 }
		--mac_conf
	ipdongleIpAddressIpv4  OBJECT-TYPE
		SYNTAX      InetAddressIPv4
		MAX-ACCESS  read-only
		STATUS      current
		DESCRIPTION
			"The current IPv4 address."
		::= { ipDongleAdmin 9 }
		--web_conf.IpV4Addr
	ipdongleSubnetIpv4  OBJECT-TYPE
		SYNTAX      InetAddressIPv4
		MAX-ACCESS  read-only
		STATUS      current
		DESCRIPTION
			"The current IPv4 subnet."
		::= { ipDongleAdmin 10 }
		--web_conf.IpV4Netmask
	ipdongleGatewayIpv4  OBJECT-TYPE
		SYNTAX      InetAddressIPv4
		MAX-ACCESS  read-only
		STATUS      current
		DESCRIPTION
			"The current IPv4 gateway"
		::= { ipDongleAdmin 11 }
		--web_conf.IpV4GatewayIP
	--
	--	ipMasterFanUnitWebAccess
	--
	ipDongleWebAccess			OBJECT IDENTIFIER ::= { ipDongle 2 }
	objectDateTime		OBJECT-TYPE
		SYNTAX		DateAndTime
		MAX-ACCESS  accessible-for-notify
		STATUS      current
		DESCRIPTION
			"RTC calendar and colck of the trap/notification is triggered"
		::= { ipDongleWebAccess 1 }
		
	userName		OBJECT-TYPE
		SYNTAX		DisplayString
		MAX-ACCESS  accessible-for-notify
		STATUS      current
		DESCRIPTION
			"Web GUI login user name"
		::= { ipDongleWebAccess 2 }
		
	webAccessIpAddress		OBJECT-TYPE
		SYNTAX		InetAddressIPv4
		MAX-ACCESS  accessible-for-notify
		STATUS      current
		DESCRIPTION
			"the web access remote ipaddress"
		::= { ipDongleWebAccess 3 }
		
	-------------------------------------------------------------------------------------------------------
	--
	--	pduAdmin
	--
	pduAdmin				OBJECT IDENTIFIER ::= { pduGroup 1 }

	pduTable        OBJECT-TYPE
		SYNTAX      SEQUENCE OF PduEntry
		MAX-ACCESS  not-accessible
		STATUS      current
		DESCRIPTION
			"Table of PDU"
		::= { pduAdmin 1 }

	pduEntry        OBJECT-TYPE
		SYNTAX      PduEntry
		MAX-ACCESS  not-accessible
		STATUS 	    current
		DESCRIPTION
			"Table entries of PDU"
		INDEX   { pduIndex }
		::= { pduTable 1 }

	PduEntry ::=
		SEQUENCE {
			pduIndex			INTEGER,
			pduModel			DisplayString,
			pduID				DisplayString,
			pduSerialNo				DisplayString,
			pduName				DisplayString,
			pduLocation			DisplayString,
			pduGroupNumber			DisplayString,
			pduMainLoadVoltage		DisplayString,
			pduMainLoadAmp			DisplayString,
			pduMainPowerFactor		DisplayString,
			pduMainActivePower		DisplayString,
			pduMainApparentPower		DisplayString,
			pduMainCumulativeEnergy		DisplayString,
			pduRealTimeClock		DisplayString,
			circuits			DisplayString,
			circuitBreakers			DisplayString,
			outlets				DisplayString,
			tHSensors			DisplayString,
			rCMSensors			DisplayString}

	pduIndex OBJECT-TYPE
		SYNTAX      INTEGER (1..32)
		MAX-ACCESS  read-only
		STATUS      current
		DESCRIPTION
			"The cascade level of this PDU (01 to 16).
			 (1)=PDU Level is 01, (2)=PDU level is 02, (16)=PDU level is 16."
		::= { pduEntry 1 }
		--PDU_Details.Device_ID (converted 2nd byte to integer)
	pduModel OBJECT-TYPE
		SYNTAX      DisplayString (SIZE (1..48))
		MAX-ACCESS  read-only
		STATUS      current
		DESCRIPTION
			"The model number of this PDU."
		::= { pduEntry 2 }
		--PDU_Details.PDU_Model
	pduID OBJECT-TYPE
		SYNTAX      DisplayString (SIZE (1..16))
		MAX-ACCESS  read-only
		STATUS      current
		DESCRIPTION
			"The unique identifier of this PDU."
		::= { pduEntry 3 }
		--PDU_Details.Serial_Number
	pduSerialNo OBJECT-TYPE
		SYNTAX      DisplayString (SIZE (1..32))
		MAX-ACCESS  read-only
		STATUS      current
		DESCRIPTION
			"The unique serial number of this PDU."
		::= { pduEntry 4 }
		--PDU_Details.serialno_32B
	pduName OBJECT-TYPE
		SYNTAX      DisplayString (SIZE (1..16))
		MAX-ACCESS  read-write
		STATUS      current
		DESCRIPTION
			"The name of this PDU.
			 SET: input length = 1 to 16 characters.
			 The valid characters are (0 to 9), (a to z), (A to Z), (_), (-) and (.)."
		::= { pduEntry 6 }
		--PDU_Details.PDU_Name
	pduLocation OBJECT-TYPE
		SYNTAX      DisplayString (SIZE (1..16))
		MAX-ACCESS  read-write
		STATUS      current
		DESCRIPTION
			"The location of this PDU.
			 SET: input length = 1 to 16 characters.
			 The valid characters are (0 to 9), (a to z), (A to Z), (_), (-) and (.)."
		::= { pduEntry 7 }
		--PDU_Details.PDU_Location
	pduGroupNumber OBJECT-TYPE
		SYNTAX      DisplayString (SIZE (3))
		MAX-ACCESS  read-write
		STATUS      current
		DESCRIPTION
			"The group number of this PDU. Ranged from 000 to 240.
			 (000)=000, (240)=240."
		::= { pduEntry 8 }
		-- updated on 2015/03/20 by Ed
	pduMainLoadVoltage OBJECT-TYPE
		SYNTAX      DisplayString (SIZE (20))
		MAX-ACCESS  read-only
		STATUS      current
		DESCRIPTION
			"The voltage measured on this PDU in tenth of Volts.
			Single phase PDU:
 			(0000)=0.0 VAC, (1100)=110.0 VAC, (2201)=220.1 VAC
			Three phase PDU:
			2204(2201,2202,2203)=1st 4 digits are the averag voltage of all circuits/banks, Phase 1 is 220.1 VAC, Phase 2 is 220.2 VAC, Phase 3 is 220.3 VAC"
		::= { pduEntry 13 }
		--PDU_Details.PDU_Load_Voltage
	pduMainLoadAmp OBJECT-TYPE
		SYNTAX      DisplayString (SIZE (1..3))
		MAX-ACCESS  read-only
		STATUS      current
		DESCRIPTION
			"The current load measured on this PDU in tenth of Amps.
			 (0)=0.0 A, (1)=0.1 A, (101)=10.1 A, (160)=16.0 A"
		::= { pduEntry 14 }
		--Circuit_Details.Circuit_Load_Amp (sum of all circuits)
	pduMainPowerFactor OBJECT-TYPE
		SYNTAX      DisplayString (SIZE (3))
		MAX-ACCESS  read-only
		STATUS      current
		DESCRIPTION
			"The power factor of this PDU in hundredth.
			 (000)=0, (001)=0.01, (010)=0.1, (100)=1.0"
		::= { pduEntry 16 }
		--PDU_Details.PDU_PowerFactor
	pduMainActivePower OBJECT-TYPE
		SYNTAX      DisplayString (SIZE (1..7))
		MAX-ACCESS  read-only
		STATUS      current
		DESCRIPTION
			"The active power consumption of this PDU in hundred-thousandth of kW.
			 Ranged from (0000000) to (9999999).
			 (0)=0 kW, (12)=0.00012 kW, (123)=0.00123 kW, (1234567)=12.34567 kW."
		::= { pduEntry 17 }
		--Circuit_Details.Circuit_ActivePower (sum of all circuits)
	pduMainApparentPower OBJECT-TYPE
		SYNTAX      DisplayString (SIZE (1..7))
		MAX-ACCESS  read-only
		STATUS      current
		DESCRIPTION
			"The apparent power consumption of this PDU in hundred-thousandth of kVA,
			 Ranged from (0000000) to (9999999).
			 (0)=0 kVA, (12)=0.00012 kVA, (123)=0.00123 kVA, (1234567)=12.34567 kVA."
		::= { pduEntry 18 }
		--Circuit_Details.Circuit_ApparentPower (sum of all circuits)
	pduMainCumulativeEnergy OBJECT-TYPE
		SYNTAX      DisplayString (SIZE (1..8))
		MAX-ACCESS  read-only
		STATUS      current
		DESCRIPTION
			"The cumulative energy (KWh) of this PDU in hundredth of kilowatt-hours.
			 (0)=0.00 KWh, (12345)=123.45 KWh, (12345678)=123456.78 KWh"
		::= { pduEntry 19 }
		--Circuit_Details.Circuit_CumulativeEnergy (sum of all circuits)
	pduRealTimeClock OBJECT-TYPE
		SYNTAX      DisplayString (SIZE (0..14))
		MAX-ACCESS  read-only
		STATUS      current
		DESCRIPTION
			"The real time clock & calendar. Formatted to 'YYMMDDHHNNSSW'
			 (1404111358305)=2014-APR-11 13:58:30, Friday"
		::= { pduEntry 20 }
	--
	--	circuits
	--
	circuits				OBJECT IDENTIFIER ::= { pduEntry 24 }

	circuitTable        OBJECT-TYPE
		SYNTAX      SEQUENCE OF CircuitTablEntry
		MAX-ACCESS  not-accessible
		STATUS      current
		DESCRIPTION
			"Table of circuit"
		::= { circuits 1 }

	circuitTablEntry        OBJECT-TYPE
		SYNTAX      CircuitTablEntry
		MAX-ACCESS  not-accessible
		STATUS 	    current
		DESCRIPTION
			"Table entries of circuit"
		INDEX   { pduIndex,
					circuitIndex }
		::= { circuitTable 1 }

	CircuitTablEntry ::=
		SEQUENCE {
			circuitIndex			INTEGER,
			circuitRatedAmp			DisplayString,
			circuitName			DisplayString,
			circuitState			INTEGER,
			circuitLoadVoltage		DisplayString,
			circuitLoadAmp			DisplayString,
			circuitPowerFactor			DisplayString,
			circuitActivePower			DisplayString,
			circuitApparentPower		DisplayString,
			circuitLoadPeakAmp		DisplayString,
			circuitCumulativeEnergy		DisplayString,
			circuitLoadPeakAmpReset		DisplayString,
			circuitBreakerStateCopy		INTEGER,
			circuitLoadAmpAlarmThresh	DisplayString,
			circuitLoadAmpRisingAlertThresh	DisplayString,
			circuitLoadAmpLowAlertThresh	DisplayString,
			circuitCumulativeEnergyReset		DisplayString
		}

	circuitIndex OBJECT-TYPE
		SYNTAX      INTEGER (1..12)
		MAX-ACCESS  read-only
		STATUS      current
		DESCRIPTION
			"The circuit ID of this circuit.
			 Single phase :
			    (1)=Circuit A, (2)=Circuit B.
			 Single phase 63A :
				(1)= Bank 1 , (2)= Bank 2 , (3)= Bank 3 , (4)=Bank 4
			 Three phase :
			    (1)=Bank 1, (2)=Bank 2, (3)=Bank 3, (4)=Bank 4, (5)=Bank 5, (6)=Bank 6,
				(7)=Bank 7, (8)=Bank 8, (9)=Bank 9, (10)=Bank 10, (11)=Bank 11, (12)=Bank 12."
		::= { circuitTablEntry 1 }

	circuitRatedAmp OBJECT-TYPE
		SYNTAX      DisplayString (SIZE (3))
		MAX-ACCESS  read-only
		STATUS      current
		DESCRIPTION
			"The input current rating of this circuit in tenth of Amps.
			 (160)=16.0 A, (200)=20.0 A."
		::= { circuitTablEntry 2 }
	circuitName OBJECT-TYPE
		SYNTAX       DisplayString (SIZE (1..16))
		MAX-ACCESS  read-only
		STATUS      current
		DESCRIPTION
			"The name of this circuit.
			 The valid characters are (0 to 9), (a to z), (A to Z), (_), (-) and (.)."
		::= { circuitTablEntry 4 }
	circuitState OBJECT-TYPE
		SYNTAX      INTEGER {
				   normal      (0),
				   alarm       (1),
				   risingAlert (2),
				   lowAlert    (3),
				   notExist    (4)
				}
		MAX-ACCESS  read-only
		STATUS      current
		DESCRIPTION
			"The status of this circuit.
			 (0)=Normal, (1)=Alarm, (2)=RisingAlert, (3)=LowAlert, (4)=Not exist"
		::= { circuitTablEntry 5 }

	circuitLoadVoltage OBJECT-TYPE
		SYNTAX      DisplayString (SIZE (4))
		MAX-ACCESS  read-only
		STATUS      current
		DESCRIPTION
			"The voltage measured on this circuit in tenth of Volts
			 (0000)=0.0 VAC, (1100)=110.0 VAC, (2201)=220.1 VAC"
		::= { circuitTablEntry 6 }

	circuitLoadAmp OBJECT-TYPE
		SYNTAX      DisplayString (SIZE (3))
		MAX-ACCESS  read-only
		STATUS      current
		DESCRIPTION
			"The current load measured on this circuit in tenth of Amps
			 (000)=0.0 A, (001)=0.1 A, (101)=10.1 A, (160)=16.0 A"
		::= { circuitTablEntry 7 }

	circuitPowerFactor OBJECT-TYPE
		SYNTAX      DisplayString (SIZE (3))
		MAX-ACCESS  read-only
		STATUS      current
		DESCRIPTION
			"The power factor measured on this circuit in hundredths"
		::= { circuitTablEntry 9 }
		
	circuitActivePower OBJECT-TYPE
		SYNTAX      DisplayString (SIZE (7))
		MAX-ACCESS  read-only
		STATUS      current
		DESCRIPTION
			"The active power consumption measured on this circuit in hundred-thousandth of kW"
		::= { circuitTablEntry 10 }
		
	circuitApparentPower OBJECT-TYPE
		SYNTAX      DisplayString (SIZE (7))
		MAX-ACCESS  read-only
		STATUS      current
		DESCRIPTION
			"The apparent power consumption  measured on this circuit in hundred-thousandth of kVA"
		::= { circuitTablEntry 11 }
		
	circuitLoadPeakAmp OBJECT-TYPE
		SYNTAX      DisplayString (SIZE (16))
		MAX-ACCESS  read-only
		STATUS      current
		DESCRIPTION
			"The the peak current measured on this circuit in tenth of Amps with timestamp.
			 (140411152059@123)=2014-APR-11 15:20:59, 12.3 Amp."
		::= { circuitTablEntry 12 }

	circuitCumulativeEnergy OBJECT-TYPE
		SYNTAX      DisplayString (SIZE (21))
		MAX-ACCESS  read-only
		STATUS      current
		DESCRIPTION
			"The cumulative energy (kWh) of this circuit in hundredth of kilowatt-hours with timestamp.
			 (140411152059@00000000)=2014-APR-11 15:20:59, 0.00 kWh.
 			 (140411152059@09999999)=2014-APR-11 15:20:59, 99999.99 kWh."
		::= { circuitTablEntry 13 }

	circuitLoadPeakAmpReset OBJECT-TYPE
		SYNTAX      DisplayString (SIZE (1))
		MAX-ACCESS  read-write
		STATUS      current
		DESCRIPTION
			"Reset the peak current of this circuit to zero.
			 SET: (1)=confirm reset"
		::= { circuitTablEntry 14 }

	circuitBreakerStateCopy OBJECT-TYPE
		SYNTAX      INTEGER {
				   normal      (0),
				   tripped     (1)
				}
		MAX-ACCESS  read-only
		STATUS      current
		DESCRIPTION
			"The circuit breaker state.
			 (0)=Normal,  (1)= Tripped."
		::= { circuitTablEntry 15 }

	circuitLoadAmpAlarmThresh OBJECT-TYPE
		SYNTAX      DisplayString (SIZE (3))
		MAX-ACCESS  read-write
		STATUS      current
		DESCRIPTION
			"The upper alarm current threshold of this circuit in tenth of Amps.
			 (000)=disable, (001)=0.1 A, (050)=5.0 A, (100)=10.0 A."
		::= { circuitTablEntry 16 }
	circuitLoadAmpRisingAlertThresh OBJECT-TYPE
		SYNTAX      DisplayString (SIZE (3))
		MAX-ACCESS  read-write
		STATUS      current
		DESCRIPTION
			"The rising alert current threshold of this circuit in tenth of Amps.
			 (000)=disable, (001)=0.1 A, (050)=5.0 A, (100)=10.0 A."
		::= { circuitTablEntry 17 }
	circuitLoadAmpLowAlertThresh OBJECT-TYPE
		SYNTAX      DisplayString (SIZE (3))
		MAX-ACCESS  read-write
		STATUS      current
		DESCRIPTION
			"The lower alert current threshold of this circuit in tenth of Amps.
			 (000)=disable, (001)=0.1 A, (050)=5.0 A, (100)=10.0 A."
		::= { circuitTablEntry 18 }

	circuitCumulativeEnergyReset OBJECT-TYPE
		SYNTAX      DisplayString (SIZE (1))
		MAX-ACCESS  read-write
		STATUS      current
		DESCRIPTION
			"Reset the cumulative energy (kWh) of this circuit to zero.
			 SET: (1)=confirm reset"
		::= { circuitTablEntry 19 }


	--
	--	circuitBreakers
	--
	circuitBreakers				OBJECT IDENTIFIER ::= { pduEntry 25 }

	circuitBreakerTable        OBJECT-TYPE
		SYNTAX      SEQUENCE OF CircuitBreakerTableEntry
		MAX-ACCESS  not-accessible
		STATUS      current
		DESCRIPTION
			"Table of circuit breaker"
		::= { circuitBreakers 1 }

	circuitBreakerTableEntry        OBJECT-TYPE
		SYNTAX      CircuitBreakerTableEntry
		MAX-ACCESS  not-accessible
		STATUS 	    current
		DESCRIPTION
			"Table entries of circuit breaker"
		INDEX   { pduIndex,
					circuitBreakerIndex }
		::= { circuitBreakerTable 1 }

	CircuitBreakerTableEntry ::=
		SEQUENCE {
			circuitBreakerIndex					INTEGER,
			circuitBreakerRatedAmp				DisplayString,
			circuitBreakerState					INTEGER
		}

	circuitBreakerIndex OBJECT-TYPE
		SYNTAX      INTEGER (1..12)
		MAX-ACCESS  read-only
		STATUS      current
		DESCRIPTION
			"The circuit breaker ID,
			Single phase:
				value (1)=circuit breaker A, (2)=circuit breaker B
			Three phase:
				value (1)=circuit breaker 1, (2)=circuit breaker 2,
				      (3)=circuit breaker 3, (4)=circuit breaker 4,
				      (5)=circuit breaker 5, (6)=circuit breaker 6,
				      (7)=circuit breaker 7, (8)=circuit breaker 8,
				      (9)=circuit breaker 9, (10)=circuit breaker 10,
				      (11)=circuit breaker 11, (12)=circuit breaker 12"

		::= { circuitBreakerTableEntry 1 }

	circuitBreakerRatedAmp OBJECT-TYPE
		SYNTAX      DisplayString (SIZE (3))
		MAX-ACCESS  read-only
		STATUS      current
		DESCRIPTION
			"The current rating of this circuit breaker in tenth of Amps.
			 (000)=0.0 A, (001)=0.1 A, (101)=10.1 A, (160)=16.0 A"
		::= { circuitBreakerTableEntry 2 }
	circuitBreakerState OBJECT-TYPE
		SYNTAX      INTEGER {
				   normal      (0),
				   tripped     (1)
				}
		MAX-ACCESS  read-only
		STATUS      current
		DESCRIPTION
			"The circuit breaker state.
			 (0)=Normal,  (1)= Tripped."
		::= { circuitBreakerTableEntry 4 }

	--
	--	outlets
	--
	outlets				OBJECT IDENTIFIER ::= { pduEntry 26 }


	stdOutletTable        OBJECT-TYPE
		SYNTAX      SEQUENCE OF StdOutletTableEntry
		MAX-ACCESS  not-accessible
		STATUS      current
		DESCRIPTION
			"Table of non C19 outlet."
		::= { outlets 1 }

	stdOutletTableEntry        OBJECT-TYPE
		SYNTAX      StdOutletTableEntry
		MAX-ACCESS  not-accessible
		STATUS 	    current
		DESCRIPTION
			"Table entries of non C19 outlet."
		INDEX   { pduIndex,
					stdOutletIndex }
		::= { stdOutletTable 1 }

	StdOutletTableEntry ::=
		SEQUENCE {
			stdOutletIndex				INTEGER,
			stdOutletCircuit			DisplayString,
			stdOutletType				DisplayString,
			stdOutletName					DisplayString,
			stdOutletPowerStatus			INTEGER,
			stdOutletAlarmState			INTEGER,
			stdOutletLoadAmp			DisplayString,
			stdOutletEnergy				DisplayString,
			stdOutletPeakAmp			DisplayString,
			stdOutletCumulativeEnergy		DisplayString,
			stdOutletLoadAmpAlarmThresh		DisplayString,
			stdOutletLoadAmpRAlertThresh		DisplayString,
			stdOutletLoadAmpLAlertThresh		DisplayString,
			stdOutletPeakAmpReset			DisplayString,
			stdOutletCumulativeEnergyReset		DisplayString,
			stdOutletPowerUpSequenceDelay		INTEGER
		}

	stdOutletIndex OBJECT-TYPE
		SYNTAX      INTEGER (1..72)
		MAX-ACCESS  read-only
		STATUS      current
		DESCRIPTION
			"The unique number of this outlet (non c19).
			 (1)=outlet 01, (2)=outlet 02 ... (48)=outlet 48.
			 Note: The default outlet SNMP polling period is 10 second."
		::= { stdOutletTableEntry 1 }

	stdOutletCircuit OBJECT-TYPE
		SYNTAX      DisplayString (SIZE (2))
		MAX-ACCESS  read-only
		STATUS      current
		DESCRIPTION
			"The circuit of this outlet belongs to.
			 Single phase:
			   (1)= Circuit A, (2)=Circuit B.
			 Three phase:
			   (1)= Circuit B1, (2)=Circuit B2
			   (3)= Circuit B3, (4)=Circuit B4
			   (5)= Circuit B5, (6)=Circuit B6.
			   (7)= Circuit B7, (8)=Circuit B8
			   (9)= Circuit B9, (10)=Circuit B10
			   (11)= Circuit B11, (12)=Circuit B12."
		::= { stdOutletTableEntry 2 }

	stdOutletType OBJECT-TYPE
		SYNTAX      DisplayString (SIZE (1))
		MAX-ACCESS  read-only
		STATUS      current
		DESCRIPTION
			"The outlet type of this outlet.
			 (1)=IEC C13, (3)=BS1363, (4)=NEMA 5-20, (5)=Schuko, (6)=AS 3112, (7)=French, (8)=60309-16A, (9)=60309-32A."			 
		::= { stdOutletTableEntry 3 }
	stdOutletName OBJECT-TYPE
		SYNTAX      DisplayString (SIZE (1..16))
		MAX-ACCESS  read-write
		STATUS      current
		DESCRIPTION
			"The name of this outlet.
			 The valid characters are (0 to 9), (a to z), (A to Z), (_), (-) and (.)."
		::= { stdOutletTableEntry 4 }

	stdOutletPowerStatus OBJECT-TYPE
		SYNTAX      INTEGER {
				   switchOff      (0),
				   switchOn       (1)
				}
		MAX-ACCESS  read-write
		STATUS      current
		DESCRIPTION
			"GET: The power state of this outlet.
			 SET: (0)=switch OFF, (1)switch ON."
		::= { stdOutletTableEntry 7 }

	stdOutletAlarmState OBJECT-TYPE
		SYNTAX      INTEGER {
				   normal      (0),
				   alarm       (1),
				   risingAlert (2),
				   lowAlert    (3),
				   notExist    (4)
				}
		MAX-ACCESS  read-only
		STATUS      current
		DESCRIPTION
			"The alarm state of this outlet.
			 (0) = normal, (1) = alarm, (2)=rising alert, (3) = low alert, (4) = not exist."
		::= { stdOutletTableEntry 8 }

	stdOutletLoadAmp OBJECT-TYPE
		SYNTAX      DisplayString (SIZE (3))
		MAX-ACCESS  read-only
		STATUS      current
		DESCRIPTION
			"The current load measured on this outlet in tenth of Amps.
			 (000)=0.0 A, (001)=0.1 A, (050)=5.0 A, (100)=10.0 A, (---)=immeasurable."
		::= { stdOutletTableEntry 9 }

	stdOutletEnergy OBJECT-TYPE
		SYNTAX      DisplayString (SIZE (1..7))
		MAX-ACCESS  read-only
		STATUS      current
		DESCRIPTION
			"The power consumption of this outlet in hundred-thousandth of kW.
			 (-)=unsupported for this outlet, (0)=0 kW, (1)=0.00001 kW, (12)=0.00012 kW, (1234567)=12.34567 kW."
		::= { stdOutletTableEntry 10 }

	stdOutletPeakAmp OBJECT-TYPE
		SYNTAX      DisplayString (SIZE (16))
		MAX-ACCESS  read-only
		STATUS      current
		DESCRIPTION
			"The peak current of this outlet in tenth of Amps. with timsstamp in <yymmddhhnnss@aab> format.
			 (yymmddhhnnss)=the timestamp when peak Amp. is measured (year, month, day, hour, minute, second).
			 (@)=seperator character to split timestamp and the peak Amp.
			 (aab)=the peak Amp. in tenth of Amps.
			 (-)=unsupported for this outlet,"
		::= { stdOutletTableEntry 11 }

	stdOutletCumulativeEnergy OBJECT-TYPE
		SYNTAX      DisplayString (SIZE (21))
		MAX-ACCESS  read-only
		STATUS      current
		DESCRIPTION
			"The cumulative energy of this outlet in hundredth of kilowatt-hours with time stapm in < yymmddhhnnss@caaaaabb > format.
			 (yymmddhhnnss)=the timestamp when start the accumulation (year, month, day, hour, minute, second).
			 (@)=sperator character to split timestamp and the cumulative energy.
			 (c)=cycle counter. If the cumulative energy over 9999999, the counter will be increased by 1 and the 	 energy is reset.
			 (aaaaabb)=the cumulative energy in hundredth of kWh.
			 (-)=unsupported for this outlet,"
		::= { stdOutletTableEntry 12 }

	stdOutletLoadAmpAlarmThresh OBJECT-TYPE
		SYNTAX      DisplayString (SIZE (3))
		MAX-ACCESS  read-write
		STATUS      current
		DESCRIPTION
			"The upper alarm current threshold of this outlet in tenth of Amps.
			 (-)=unsupported for this outlet, (000)=0.0 A, (001)=0.1 A, (050)=5.0 A, (100)=10.0 A."
		::= { stdOutletTableEntry 13 }
		-- Added on 2013/04/08

	stdOutletLoadAmpRAlertThresh OBJECT-TYPE
		SYNTAX      DisplayString (SIZE (3))
		MAX-ACCESS  read-write
		STATUS      current
		DESCRIPTION
			"The rising alert current threshold of this outlet in tenth of Amps.
			 (-)=unsupported for this outlet, (000)=disable, (001)=0.1 A, (050)=5.0 A, (100)=10.0 A."
		::= { stdOutletTableEntry 14 }
		-- Added on 2015/05/05

	stdOutletLoadAmpLAlertThresh OBJECT-TYPE
		SYNTAX      DisplayString (SIZE (3))
		MAX-ACCESS  read-write
		STATUS      current
		DESCRIPTION
			"The lower alert current threshold of this outlet in tenth of Amps.
			 (-)=unsupported for this outlet, (000)=disable, (001)=0.1 A, (050)=5.0 A, (100)=10.0 A."
		::= { stdOutletTableEntry 15 }
		-- Added on 2013/04/08

	stdOutletPeakAmpReset OBJECT-TYPE
		SYNTAX      DisplayString (SIZE (1))
		MAX-ACCESS  read-write
		STATUS      current
		DESCRIPTION
			"Reset the peak current of this outlet to zero.
			 (1)=confirm reset."
		::= { stdOutletTableEntry 16 }

	stdOutletCumulativeEnergyReset OBJECT-TYPE
		SYNTAX      DisplayString (SIZE (1))
		MAX-ACCESS  read-write
		STATUS      current
		DESCRIPTION
			"Reset the cumulative energy consumption counter of this outlet to zero,
			 (1)=confirm reset."
		::= { stdOutletTableEntry 17 }

	stdOutletPowerUpSequenceDelay OBJECT-TYPE
		SYNTAX      INTEGER (0..9)
		MAX-ACCESS  read-write
		STATUS      current
		DESCRIPTION
			"The power up sequence delay of this outlet in seconds.
			 (0)=1 second delay for swtiching ON this outlet.
			 (1)=2 second delay for swtiching ON this outlet.
			 ...
			 (9)=10 second delay for swtiching ON this outlet."
		::= { stdOutletTableEntry 18 }


	--	c19OutletTable
	c19OutletTable        OBJECT-TYPE
		SYNTAX      SEQUENCE OF C19OutletTableEntry
		MAX-ACCESS  not-accessible
		STATUS      current
		DESCRIPTION
			"Table of C19 outlet."
		::= { outlets 2 }

	c19OutletTableEntry        OBJECT-TYPE
		SYNTAX      C19OutletTableEntry
		MAX-ACCESS  not-accessible
		STATUS 	    current
		DESCRIPTION
			"Table entries of C19 outlet."
		INDEX   { pduIndex,
					c19OutletIndex }
		::= { c19OutletTable 1 }

	C19OutletTableEntry ::=
		SEQUENCE {
			c19OutletIndex				INTEGER,
			c19OutletCircuit			DisplayString,
			c19OutletType				DisplayString,
			c19OutletName					DisplayString,
			c19OutletPowerStatus			INTEGER,
			c19OutletAlarmState			INTEGER,
			c19OutletLoadAmp			DisplayString,
			c19OutletEnergy				DisplayString,
			c19OutletPeakAmp			DisplayString,
			c19OutletCumulativeEnergy		DisplayString,
			c19OutletLoadAmpAlarmThresh		DisplayString,
			c19OutletLoadAmpRAlertThresh	DisplayString,
			c19OutletLoadAmpLAlertThresh		DisplayString,
			c19OutletPeakAmpReset			DisplayString,
			c19OutletCumulativeEnergyReset		DisplayString,
			c19OutletPowerUpSequenceDelay		INTEGER
		}

	c19OutletIndex OBJECT-TYPE
		SYNTAX      INTEGER (1..72)
		MAX-ACCESS  read-only
		STATUS      current
		DESCRIPTION
			"The unique number of this outlet (C19 outlets).
			 (1)=C1, 1st C19 outlet on this pdu.
			 (2)=C2, 2nd C19 outlet on this pdu.
			 ...
			 (C9)=C9, 9th C19 outlet on this pdu."
		::= { c19OutletTableEntry 1 }

	c19OutletCircuit OBJECT-TYPE
		SYNTAX      DisplayString (SIZE (2))
		MAX-ACCESS  read-only
		STATUS      current
		DESCRIPTION
			"The circuit of this outlet belongs to.
			 Single phase:
			   (1)= Circuit A, (2)=Circuit B.
			 Three phase:
			   (1)= Circuit B1, (2)=Circuit B2
			   (3)= Circuit B3, (4)=Circuit B4
			   (5)= Circuit B5, (6)=Circuit B6.
			   (7)= Circuit B7, (8)=Circuit B8
			   (9)= Circuit B9, (10)=Circuit B10
			   (11)= Circuit B11, (12)=Circuit B12."
		::= { c19OutletTableEntry 2 }

	c19OutletType OBJECT-TYPE
		SYNTAX      DisplayString (SIZE (1))
		MAX-ACCESS  read-only
		STATUS      current
		DESCRIPTION
			"The outlet type of this outlet.
			 (1)=IEC C13, (2)=IEC C19, (3)=BS1363, (4)=NEMA 5-20R, (5)=CEE7."
		::= { c19OutletTableEntry 3 }
	c19OutletName OBJECT-TYPE
		SYNTAX      DisplayString (SIZE (0..16))
		MAX-ACCESS  read-write
		STATUS      current
		DESCRIPTION
			"The name of this outlet.
			 The valid characters are (0 to 9), (a to z), (A to Z), (_), (-) and (.)."
		::= { c19OutletTableEntry 4 }

	c19OutletPowerStatus OBJECT-TYPE
		SYNTAX      INTEGER {
				   switchOff      (0),
				   switchOn       (1)
				}
		MAX-ACCESS  read-write
		STATUS      current
		DESCRIPTION
			"GET: The power state of this outlet.
			 SET:  (0)=switch OFF, (1)=switch ON."
		::= { c19OutletTableEntry 7 }

	c19OutletAlarmState OBJECT-TYPE
		SYNTAX      INTEGER {
				   normal      (0),
				   alarm       (1),
				   risingAlert (2),
				   lowAlert    (3),
				   notExist    (4)
				}
		MAX-ACCESS  read-only
		STATUS      current
		DESCRIPTION
			"The alarm state of this outlet.
			 (0) = normal, (1) = alarm, (2)=rising alert, (3) = low alert, (4) = not exist."
		::= { c19OutletTableEntry 8 }

	c19OutletLoadAmp OBJECT-TYPE
		SYNTAX      DisplayString (SIZE (0..3))
		MAX-ACCESS  read-only
		STATUS      current
		DESCRIPTION
			"The current load measured on this outlet in tenth of Amps.
			 (000)=0.0 A, (001)=0.1 A, (050)=5.0 A, (100)=10.0 A, (---)=immeasurable."
		::= { c19OutletTableEntry 9 }

	c19OutletEnergy OBJECT-TYPE
		SYNTAX      DisplayString (SIZE (0..7))
		MAX-ACCESS  read-only
		STATUS      current
		DESCRIPTION
			"The power consumption for this outlet in hundred-thousandth of kW.
			 (-)=unsupported for this outlet, (0)=0 W, (1)=0.00001 kW, (12)=0.00012 kW, (1234567)=12.34567 kW."
		::= { c19OutletTableEntry 10 }

	c19OutletPeakAmp OBJECT-TYPE
		SYNTAX      DisplayString (SIZE (16))
		MAX-ACCESS  read-only
		STATUS      current
		DESCRIPTION
			"The peak current of this outlet in tenth of Amps. with timsstamp in <yymmddhhnnss@aab> format.
			 (yymmddhhnnss)=the timestamp when peak Amp. is measured (year, month, day, hour, minute, second).
			 (@)=sperator character to split timestamp and the peak Amp.
			 (aab)=the peak Amp. in tenth of Amps.
			 (-)=unsupported for this outlet."
		::= { c19OutletTableEntry 11 }

	c19OutletCumulativeEnergy OBJECT-TYPE
		SYNTAX      DisplayString (SIZE (21))
		MAX-ACCESS  read-only
		STATUS      current
		DESCRIPTION
			"The cumulative energy of this outlet in hundredth of kilowatt-hours with time stapm in < yymmddhhnnss@caaaaabb > format.
			 (yymmddhhnnss)=the timestamp when start the accumulation (year, month, day, hour, minute, second).
			 (@)=sperator character to split timestamp and the cumulative energy.
			 (c)=cycle counter. If the cumulative energy over 9999999, the counter will incerased by 1 and the cumulative energy is reset.
			 (aaaaabb)=the cumulative energy in hundredth of kWh.
			 (-)=unsupported for this outlet.
			 Note: The default outlet SNMP polling period is 10 second."
		::= { c19OutletTableEntry 12 }

	c19OutletLoadAmpAlarmThresh OBJECT-TYPE
		SYNTAX      DisplayString (SIZE (3))
		MAX-ACCESS  read-write
		STATUS      current
		DESCRIPTION
			"The upper alarm current threshold of this outlet in tenth of Amps.
			 (-)=unsupported for this outlet, (000)=0.0 A, (001)=0.1 A, (050)=5.0 A, (100)=10.0 A."
		::= { c19OutletTableEntry 13 }
		-- Added on 2013/04/09
	c19OutletLoadAmpRAlertThresh OBJECT-TYPE
		SYNTAX      DisplayString (SIZE (3))
		MAX-ACCESS  read-write
		STATUS      current
		DESCRIPTION
			"The upper rising alert current threshold of this outlet in tenth of Amps.
			 (-)=unsupported for this outlet, (000)=0.0 A, (001)=0.1 A, (050)=5.0 A, (100)=10.0 A."
		::= { c19OutletTableEntry 14 }
		-- Added on 2015/05/05
	c19OutletLoadAmpLAlertThresh OBJECT-TYPE
		SYNTAX      DisplayString (SIZE (3))
		MAX-ACCESS  read-write
		STATUS      current
		DESCRIPTION
			"The lower alert current threshold of this outlet in tenth of Amps.
			 (-)=unsupported for this outlet, (000)=disable, (001)=0.1 A, (050)=5.0 A, (100)=10.0 A."
		::= { c19OutletTableEntry 15 }
		-- Added on 2013/04/09

	c19OutletPeakAmpReset OBJECT-TYPE
		SYNTAX      DisplayString (SIZE (1))
		MAX-ACCESS  read-write
		STATUS      current
		DESCRIPTION
			"Reset the peak current of this outlet to zero.
			 (1)=confirm reset."
		::= { c19OutletTableEntry 16 }

	c19OutletCumulativeEnergyReset OBJECT-TYPE
		SYNTAX      DisplayString (SIZE (1))
		MAX-ACCESS  read-write
		STATUS      current
		DESCRIPTION
			"Reset the cumulative energy consumption counter of this outlet to zero,
			 (1)=confirm reset."
		::= { c19OutletTableEntry 17 }

	c19OutletPowerUpSequenceDelay OBJECT-TYPE
		SYNTAX      INTEGER (0..9)
		MAX-ACCESS  read-write
		STATUS      current
		DESCRIPTION
			"The power up sequence delay of this outlet in seconds.
			 (0)=1 second delay for swtiching ON this outlet.
			 (1)=2 second delay for swtiching ON this outlet.
			 ...
			 (9)=10 second delay for swtiching ON this outlet."
		::= { c19OutletTableEntry 18 }

	--
	--	Sensors
	--
	tHSensors				OBJECT IDENTIFIER ::= { pduEntry 27 }

	tHSensorTable        OBJECT-TYPE
		SYNTAX      SEQUENCE OF THSensorTableEntry
		MAX-ACCESS	not-accessible
		STATUS      current
		DESCRIPTION
			"Table of THsensor"
		::= { tHSensors 1 }

	tHSensorTableEntry        OBJECT-TYPE
		SYNTAX      THSensorTableEntry
		MAX-ACCESS  not-accessible
		STATUS 	    current
		DESCRIPTION
			"Table entries of THSensor(sensor: Temp. only, Temp+Humid., Door, Air flow, Smoke sensor)"
		INDEX   { pduIndex,
					tHSensorIndex }
		::= { tHSensorTable 1 }

	THSensorTableEntry ::=
		SEQUENCE {
			tHSensorIndex						INTEGER,
			tHSensorLocation					DisplayString,
			tHSensorType						DisplayString,
			tHSensorConnState					INTEGER,
			tHSensorAlarmState					DisplayString,
			tempSensorValue						INTEGER,
			tempSensorValueStr					DisplayString,
			tempSensorUpperAlarmThresh			DisplayString,
			tempSensorLowerAlarmThresh			DisplayString,
			humiSensorValue						INTEGER,
			humiSensorValueStr					DisplayString,
			humiSensorUpperAlarmThresh			DisplayString,
			humiSensorLowerAlarmThresh			DisplayString,
			tHSensorActivation					INTEGER
		}

	tHSensorIndex OBJECT-TYPE
		SYNTAX      INTEGER (1..2)
		MAX-ACCESS  read-only
		STATUS      current
		DESCRIPTION
			"The id of the sensor port.
			 (1)=TH1, (2)=TH2."
		::= { tHSensorTableEntry 1 }
	tHSensorLocation OBJECT-TYPE
		SYNTAX      DisplayString (SIZE (0..16))
		MAX-ACCESS  read-write
		STATUS      current
		DESCRIPTION
			"The location of the sensor.
			 The valid characters are (0 to 9), (a to z), (A to Z), (_), (-) and (.)."
		::= { tHSensorTableEntry 3 }

	tHSensorType OBJECT-TYPE
		SYNTAX      DisplayString (SIZE (1))
		MAX-ACCESS  read-only
		STATUS      current
		DESCRIPTION
			"The sensor type.
			 (1)=Temperature sensor,
			 (2)=Temperature-Humidity sensor,
			 (3)=Door sensor,
			 (4)=Air flow sensor,
			 (5)=Smoke sensor."
		::= { tHSensorTableEntry 4 }

	tHSensorConnState OBJECT-TYPE
		SYNTAX      INTEGER {
				   disconnected    (0),
				   connected       (1)
				}
		MAX-ACCESS  read-only
		STATUS      current
		DESCRIPTION
			"The connection status of this sensor.
			 (0)=disconnected, (1)=connected."
		::= { tHSensorTableEntry 5 }

	tHSensorAlarmState OBJECT-TYPE
		SYNTAX      DisplayString (SIZE (1..2))
		MAX-ACCESS  read-only
		STATUS      current
		DESCRIPTION
			"2 digit, first digit = temperature status & second digit = humidity status.
			 For tHSensorType is (1) :
			   (0)=Normal,
			  (10)=Temp. alarm only
			 For tHSensorType is (2) :
			   (0)=Normal,
			  (10)=Temp. alarm only,
			  (11)=Temp. & Humid alarm.
			 For tHSensorType is (3) :
			   (0)=Door close,
			  (10)=Door open.
			 For tHSensorType is (4) :
			   (0)=Air flow normal,
			  (10)=Air flow alarm.
			 For tHSensorType is (5) :
			   (0)=Smoke normal,
			  (10)=Smoke alarm."
		::= { tHSensorTableEntry 6 }

	tempSensorValue OBJECT-TYPE
		SYNTAX      INTEGER (0..999)
		MAX-ACCESS  read-only
		STATUS      current
		DESCRIPTION
			"For tHSensorType is (1) or (2) :
			  The temperature measured in tenth of Degree Celsius.
			  (0)=0'C, (10)=1'C, (123)=12.3'C, (999)=99.9'C.
			 For tHSensorType is (3) :
			  The door sensor status.
			  (48)=Door open
			  (49)=Door close.
			 For tHSensorType is (4) :
			   The air flow volume flow rate measured in tenth of cubic feet per minute(CFM).
			   (0)=0cfm, (10)=1cfm, (123)=12.3cfm, (999)=99.9cfm.
			 For tHSensorType is (5)
			   The smoke sensor status.
			   (48)=Smoke alarm,
			   (49)=Smoke normal."
		::= { tHSensorTableEntry 7 }

	tempSensorValueStr OBJECT-TYPE
		SYNTAX      DisplayString (SIZE (4))
		MAX-ACCESS  read-only
		STATUS      current
		DESCRIPTION
			"For tHSensorType is (1) or (2) :
			  The temperature reading, in tenth of Degree Celsius.
			  (----)=disconnected, (0000)=0'C, (0010)=1'C, (0123)=12.3'C, (0999)=99.9'C.
			 For tHSensorType is (3) :
			  The door sensor status.
			  (0048)=Door open
			  (0049)=Door close.
			 For tHSensorType is (4) :
			   The air flow volume flow rate measured in tenth of cubic feet per minute(CFM).
			   (0000)=0cfm, (0010)=1cfm, (0123)=12.3cfm, (0999)=99.9cfm.
			 For tHSensorType is (5) :
			   The smoke sensor status.
			   (0048)=Smoke alarm,
			   (0049)=Smoke normal."
		::= { tHSensorTableEntry 8 }

	tempSensorUpperAlarmThresh OBJECT-TYPE
		SYNTAX      DisplayString (SIZE (4))
		MAX-ACCESS  read-write
		STATUS      current
		DESCRIPTION
			"The temperature upper alarm threshold in tenth of Degree Celsius.
			 (0000)=0'C, (0010)=1'C, (0123)=12.3'C, (0999)=99.9'C.
			 *Available for tHSensorType is (1), (2) or (4)."
		::= { tHSensorTableEntry 9 }
	tempSensorLowerAlarmThresh OBJECT-TYPE
		SYNTAX      DisplayString (SIZE (4))
		MAX-ACCESS  read-only
		STATUS      current
		DESCRIPTION
			"The temperature low alert threshold in tenth of Degree Celsius.
			 (0000)=0'C, (0010)=1'C, (0123)=12.3'C, (0999)=99.9'C.
			 *Available for tHSensorType is (1), (2) or (4)."
		::= { tHSensorTableEntry 10 }
	humiSensorValue OBJECT-TYPE
		SYNTAX      INTEGER (0..999)
		MAX-ACCESS  read-only
		STATUS      current
		DESCRIPTION
			"The relative humidity measured in tenth of percent.
			 (0)=0%, (1)=0.1%, (12)=1.2%, (123)=12.3%, (999)=99.9%"
		::= { tHSensorTableEntry 11 }

	humiSensorValueStr OBJECT-TYPE
		SYNTAX      DisplayString (SIZE (3))
		MAX-ACCESS  read-only
		STATUS      current
		DESCRIPTION
			"The relative humidity measured in tenth of percent.
			 (---)=immeasurable or disconnected,
			 (000)=0%, (001)=0.1%, (012)=1.2%, (123)=12.3%, (999)=99.9%"
		::= { tHSensorTableEntry 12 }

	humiSensorUpperAlarmThresh OBJECT-TYPE
		SYNTAX      DisplayString (SIZE (3))
		MAX-ACCESS  read-write
		STATUS      current
		DESCRIPTION
			"The relative humidity upper alarm threshold in tenth of percent.
			 (---)=immeasurable or disconnected,
			 (000)=0%, (001)=0.1%, (012)=1.2%, (123)=12.3%, (999)=99.9%"
		::= { tHSensorTableEntry 13 }
	humiSensorLowerAlarmThresh OBJECT-TYPE
		SYNTAX      DisplayString (SIZE (3))
		MAX-ACCESS  read-only
		STATUS      current
		DESCRIPTION
			"The relative humidity low alert threshold in tenth of percent.
			 (---)=immeasurable or disconnected,
			 (000)=0%, (001)=0.1%, (012)=1.2%, (123)=12.3%, (999)=99.9%"
		::= { tHSensorTableEntry 14 }
		
	tHSensorActivation OBJECT-TYPE
		SYNTAX      INTEGER {
				   deactivated      (0),
				   actvated       (1)
				}
		MAX-ACCESS  read-write
		STATUS      current
		DESCRIPTION
			"The activation state of the sensor: (0)=Deactivated. (1)=Actvated"
		::= { tHSensorTableEntry 15 }

	--
	--	pduTraps
	--
	pduTraps	OBJECT IDENTIFIER	::= { pduGroup 2 }

	circuitLoadEventTriggered		NOTIFICATION-TYPE
		OBJECTS {
			pduIndex, pduName, pduLocation, circuitIndex, circuitState,circuitLoadAmp, circuitLoadAmpAlarmThresh, circuitLoadAmpRisingAlertThresh, circuitLoadAmpLowAlertThresh
		}
		STATUS      current
		DESCRIPTION
			"The circuit current upper alarm of this PDU triggered.
			 The trap sends out within 2 mins in cycle( 16 level PDUs connected ) until the current reading returns below the circuitLoadAmpAlarmThresh."
		::= { pduTraps 1 }

	circuitBreakerTripped		NOTIFICATION-TYPE
		OBJECTS {
			pduIndex, pduName, pduLocation, circuitBreakerIndex, circuitBreakerState
		}
		STATUS      current
		DESCRIPTION
			"The circuit breaker of this PDU tripped
			 The trap sends out within 2 mins in cycle ( 16 level PDUs connected )."
		::= { pduTraps 12 }

	circuitBreakerRecovered		NOTIFICATION-TYPE
		OBJECTS {
			pduIndex, pduName, pduLocation, circuitBreakerIndex, circuitBreakerState
		}
		STATUS      current
		DESCRIPTION
			"The circuit breaker of this PDU recovered.
			 The trap sends out once within 2 mins ( 16 level PDUs connected )."
		::= { pduTraps 13 }

	sensorConnectionLost		NOTIFICATION-TYPE
		OBJECTS {
			pduIndex, pduName, pduLocation, tHSensorIndex, tHSensorType, tHSensorLocation
		}
		STATUS      current
		DESCRIPTION
			"The sensor (temperature, temperature-humidity, door, air flow or smoke) disconnected
			 The trap sends out within 2 mins in cycle ( 16 level PDUs connected ) until the sensor is reconnected."
		::= { pduTraps 40 }

	tempSensorEventTriggered		NOTIFICATION-TYPE
		OBJECTS {
			pduIndex, pduName, pduLocation, tHSensorIndex, tHSensorType, tHSensorLocation, tHSensorAlarmState, tempSensorValueStr, tempSensorUpperAlarmThresh, tempSensorLowerAlarmThresh
		}
		STATUS      current
		DESCRIPTION
			"The sennor(temperature, temperature-humidity, door, air flow or smoke) alarm triggered
			 The trap sends out within 2 mins in cycle ( 16 level PDUs connected ) until the sensor reading returns below the tempSensorUpperAlarmThresh."
		::= { pduTraps 41 }


	humiSensorEventTriggered		NOTIFICATION-TYPE
		OBJECTS {
			pduIndex, pduName, pduLocation, tHSensorIndex, tHSensorType, tHSensorLocation, tHSensorAlarmState, humiSensorValueStr, humiSensorUpperAlarmThresh, humiSensorLowerAlarmThresh
		}
		STATUS      current
		DESCRIPTION
			"The relative humidity upper alarm triggered
			 The trap sends out within 2 mins in cycle ( 16 level PDUs connected ) until the relative humidity reading returns below the humiSensorUpperAlarmThresh.."
		::= { pduTraps 47 }

	--pduDisconnected		NOTIFICATION-TYPE
	pduConnectionLost		NOTIFICATION-TYPE
		OBJECTS {
			pduIndex, pduName, pduLocation
		}
		STATUS      current
		DESCRIPTION
			"The pdu is disconnected
			 The trap sends out within 2 mins in cycle ( 16 level PDUs connected ) until the PDU is reconnected."
		::= { pduTraps 53 }
	-- supported since v4.2.0	
	circuitLoadEventCleared		NOTIFICATION-TYPE
		OBJECTS {
			pduIndex, pduName, pduLocation, circuitIndex, circuitState,circuitLoadAmp, circuitLoadAmpAlarmThresh, circuitLoadAmpRisingAlertThresh, circuitLoadAmpLowAlertThresh
		}
		STATUS      current
		DESCRIPTION
			"The circuit status has been resumed to normal.
			 The trap sends out once on the event is triggered."
		::= { pduTraps 2 }
	-- supported since v4.2.0	
	sensorConnectionRecovered		NOTIFICATION-TYPE
		OBJECTS {
			pduIndex, pduName, pduLocation, tHSensorIndex, tHSensorType, tHSensorLocation
		}
		STATUS      current
		DESCRIPTION
			"Connection to the temperature or temperature-humidity sensor has been restored.
			 The trap sends out once on the event is triggered."
		::= { pduTraps 39 }
	-- supported since v4.2.0	
	tempSensorEventCleared		NOTIFICATION-TYPE
		OBJECTS {
			pduIndex, pduName, pduLocation, tHSensorIndex, tHSensorType, tHSensorLocation, tHSensorAlarmState, tempSensorValueStr, tempSensorUpperAlarmThresh, tempSensorLowerAlarmThresh
		}
		STATUS      current
		DESCRIPTION
			"The temperature sensor status has been resumed to normal.
			 The trap sends out once on the event is triggered."
		::= { pduTraps 42 }
	-- supported since v4.2.0	
	humiSensorEventCleared		NOTIFICATION-TYPE
		OBJECTS {
			pduIndex, pduName, pduLocation, tHSensorIndex, tHSensorType, tHSensorLocation, tHSensorAlarmState, humiSensorValueStr, humiSensorUpperAlarmThresh, humiSensorLowerAlarmThresh
		}
		STATUS      current
		DESCRIPTION
			"The relative humidity sensor status has been resume to normal.
			 The trap sends out once on the event is triggered."
		::= { pduTraps 48 }
	-- supported since v4.2.0		
	pduConnectionRecovered		NOTIFICATION-TYPE
		OBJECTS {
			pduIndex, pduName, pduLocation
		}
		STATUS      current
		DESCRIPTION
			"Connection to the PDU has been restored.
			 The trap sends out once on the event is triggered."
		::= { pduTraps 54 }		
	feedConnectionRecovered		NOTIFICATION-TYPE
		OBJECTS {
			pduIndex, pduName, pduLocation, feedIndex
		}
		STATUS      current
		DESCRIPTION
			"Connection to the feed of this PDU has been restored."
		::= { pduTraps 55 }		
	feedConnectionLost		NOTIFICATION-TYPE
		OBJECTS {
			pduIndex, pduName, pduLocation, feedIndex
		}
		STATUS      current
		DESCRIPTION
			"The feed of this pdu is disconnected"
		::= { pduTraps 56 }
	feedIndex OBJECT-TYPE
		SYNTAX      INTEGER (0..2)
		MAX-ACCESS  accessible-for-notify
		STATUS      current
		DESCRIPTION
			"The id of the feed index.
			 (0)=Single Feed PDU, (1)=PDU-I, (2)=PDU-II."
		::= { pduTraps 99 }

	--	rcmSensor Traps Edc@20190530
	rcmSensorEventTriggered		NOTIFICATION-TYPE
		OBJECTS {
			pduIndex, pduName, pduLocation, rCMSensorIndex, rCMSensorLocation, rCMSensorAlarmState, rCMSensorReading, rCMSensorAlarmThresh, rCMSensorRisingAlertThresh, rCMSensorLowAlertThresh
		}
		STATUS      current
		DESCRIPTION
			"The RCM sensor upper alarm triggered
			 The trap sends out within 2 mins in cycle ( 16 level PDUs connected ) until rcmSensorEventCleared."
		::= { pduTraps 80 }
	rcmSensorEventCleared		NOTIFICATION-TYPE
		OBJECTS {
			pduIndex, pduName, pduLocation, rCMSensorIndex, rCMSensorLocation, rCMSensorAlarmState, rCMSensorReading, rCMSensorAlarmThresh, rCMSensorRisingAlertThresh, rCMSensorLowAlertThresh
		}
		STATUS      current
		DESCRIPTION
			"The RCM sensor status has been resume to normal.
			 The trap sends out once on the event is triggered."
		::= { pduTraps 81 }
	rcmSensorConnectionLost		NOTIFICATION-TYPE
		OBJECTS {
			pduIndex, pduName, pduLocation, rCMSensorIndex, rCMSensorLocation
		}
		STATUS      current
		DESCRIPTION
			"The RCM sensor disconnected
			 The trap sends out within 2 mins in cycle ( 16 level PDUs connected ) until rcmSensorConnectionRecovered."
		::= { pduTraps 82 }
	rcmSensorConnectionRecovered		NOTIFICATION-TYPE
		OBJECTS {
			pduIndex, pduName, pduLocation, rCMSensorIndex, rCMSensorLocation
		}
		STATUS      current
		DESCRIPTION
			"Connection to the RCM sensor has been restored.
			 The trap sends out once on the event is triggered."
		::= { pduTraps 83 }
		
	--DoorSensor
	doorSensorEventTriggered		NOTIFICATION-TYPE
		OBJECTS {
			pduIndex, pduName, pduLocation, tHSensorIndex, tHSensorType, tHSensorLocation, tHSensorAlarmState
		}
		STATUS      current
		DESCRIPTION
			"The door open triggered."
		::= { pduTraps 61 }
	doorSensorEventCleared		NOTIFICATION-TYPE
		OBJECTS {
			pduIndex, pduName, pduLocation, tHSensorIndex, tHSensorType, tHSensorLocation, tHSensorAlarmState
		}
		STATUS      current
		DESCRIPTION
			"The door sensor status has been resumed to normal(close)."
		::= { pduTraps 62 }
	--SmokeSensor
	smokeSensorEventTriggered		NOTIFICATION-TYPE
		OBJECTS {
			pduIndex, pduName, pduLocation, tHSensorIndex, tHSensorType, tHSensorLocation, tHSensorAlarmState
		}
		STATUS      current
		DESCRIPTION
			"The smoke alarm triggered"
		::= { pduTraps 63 }
	smokeSensorEventCleared		NOTIFICATION-TYPE
		OBJECTS {
			pduIndex, pduName, pduLocation, tHSensorIndex, tHSensorType, tHSensorLocation, tHSensorAlarmState
		}
		STATUS      current
		DESCRIPTION
			"The smoke sensor status has been resumed to normal"
		::= { pduTraps 64 }	
	
	
	--
	--	webLoginTraps
	--
	webLoginTraps	OBJECT IDENTIFIER	::= { ipDongle 3 }		
	webLogin		NOTIFICATION-TYPE
		OBJECTS {
			objectDateTime, userName, webAccessIpAddress
		}
		STATUS      current
		DESCRIPTION
			"The webUI login logging.
			 The trap sends out once on the event is triggered."
		::= { webLoginTraps 1 }	

	-------------------------------------------------------------------------------------------------------
	--
	--	atsAdmin
	--
	atsAdmin				OBJECT IDENTIFIER ::= { atsGroup 1 }

	atsTable        OBJECT-TYPE
		SYNTAX      SEQUENCE OF AtsEntry
		MAX-ACCESS  not-accessible
		STATUS      current
		DESCRIPTION
			"Table of PDU"
		::= { atsAdmin 1 }

	atsEntry        OBJECT-TYPE
		SYNTAX      AtsEntry
		MAX-ACCESS  not-accessible
		STATUS 	    current
		DESCRIPTION
			"Table entries of ATS"
		INDEX   { atsIndex }
		::= { atsTable 1 }

	AtsEntry ::=
		SEQUENCE {
			atsIndex			INTEGER,
			atsModel			DisplayString,
			atsID				DisplayString,
			atsName				DisplayString,
			atsLocation			DisplayString,
			atsInputSwitch		INTEGER,
			atsFeedPrimaryStatus		INTEGER,
			atsFeedSecondaryStatus		INTEGER,
			atsOutputFromFeed    		INTEGER,
			atsTotalLoadAmp    			INTEGER,
			atsOverLoadThreshold    	INTEGER,
			atsOverLoadStage    		INTEGER,
			atsConnection        		INTEGER}

	atsIndex OBJECT-TYPE
		SYNTAX      INTEGER (1..32)
		MAX-ACCESS  read-only
		STATUS      current
		DESCRIPTION
			"The cascade level of this ATS (01 to 16).
			 (1)=ATS Level is 01, (2)=aTS level is 02, (16)=ATS level is 16."
		::= { atsEntry 1 }
		--tb_ATS.Device_ID (converted 2nd byte to integer)
	atsModel OBJECT-TYPE
		SYNTAX      DisplayString (SIZE (1..48))
		MAX-ACCESS  read-only
		STATUS      current
		DESCRIPTION
			"The model number of this ATS."
		::= { atsEntry 2 }
		--tb_ATS.PDU_Model
	atsID OBJECT-TYPE
		SYNTAX      DisplayString (SIZE (1..16))
		MAX-ACCESS  read-only
		STATUS      current
		DESCRIPTION
			"The unique identifier of this ATS."
		::= { atsEntry 3 }
		--tb_ATS.Serial_Number
	atsName OBJECT-TYPE
		SYNTAX      DisplayString (SIZE (1..16))
		MAX-ACCESS  read-write
		STATUS      current
		DESCRIPTION
			"The name of this ATS.
			 SET: input length = 1 to 16 characters.
			 The valid characters are (0 to 9), (a to z), (A to Z), (_), (-) and (.)."
		::= { atsEntry 4 }
		--tb_ATS.PDU_Name
	atsLocation OBJECT-TYPE
		SYNTAX      DisplayString (SIZE (1..16))
		MAX-ACCESS  read-write
		STATUS      current
		DESCRIPTION
			"The location of this ATS.
			 SET: input length = 1 to 16 characters.
			 The valid characters are (0 to 9), (a to z), (A to Z), (_), (-) and (.)."
		::= { atsEntry 5 }
		--tb_ATS.PDU_Location
	atsInputSwitch OBJECT-TYPE
		SYNTAX      INTEGER {
				   primary      (0),
				   secondary    (1)
				}
		MAX-ACCESS  read-write
		STATUS      current
		DESCRIPTION
			"GET: The input switch of this ATS.
			 SET: (0)=switch input feed to Primary, (1)=switch input feed to Secondary.
			       UNAVAILABLE when atsOverLoadStage is overLoad."
		::= { atsEntry 6 }
		--tb_ATS.(ATS_LastInputTriggerBy, ATS_Local_Input_Setting, ATS_Remote_Input_Setting)
	atsFeedPrimaryStatus OBJECT-TYPE
		SYNTAX      INTEGER {
				   offline      (0),
				   online       (1)
				}
		MAX-ACCESS  read-only
		STATUS      current
		DESCRIPTION
			"The status of the Primary feed.
             (0)=Offline, (1)=Online."
		::= { atsEntry 7 }
		--tb_ATS.ATS_Feed_Primary_Status
	atsFeedSecondaryStatus OBJECT-TYPE
		SYNTAX      INTEGER {
				   offline      (0),
				   online       (1)
				}
		MAX-ACCESS  read-only
		STATUS      current
		DESCRIPTION
			"The status of the Secondary feed.
             (0)=Offline, (1)=Online."
		::= { atsEntry 8 }
		--tb_ATS.ATS_Feed_Secondary_Status
	atsOutputFromFeed OBJECT-TYPE
		SYNTAX      INTEGER {
				   primary      (0),
				   secondary    (1)
				}
		MAX-ACCESS  read-only
		STATUS      current
		DESCRIPTION
			"The output status of this ATS.
			 (0)=output from Primary feed, (1)=output from Secondary feed."
		::= { atsEntry 9 }
		--tb_ATS.ATS_OutputFromFeed
	atsTotalLoadAmp OBJECT-TYPE
		SYNTAX      INTEGER  (0..999)
		MAX-ACCESS  read-only
		STATUS      current
		DESCRIPTION
			"The total loading amp of this ATS in tenth of amp.
			 (0)=0.0A. (999)=99.9A"
		::= { atsEntry 10 }
		--(sum of circuits loading amp)
	atsOverLoadThreshold OBJECT-TYPE
		SYNTAX      INTEGER  (0..999)
		MAX-ACCESS  read-only
		STATUS      current
		DESCRIPTION
			"The over load alarm threshold of this ATS in tenth of amp.
			 (0)=0.0A. (999)=99.9A"
		::= { atsEntry 11 }
		--tb_ATS.OverLoadAmp
	atsOverLoadStage OBJECT-TYPE
		SYNTAX      INTEGER {
				   normal      (0),
				   overLoad    (1)
				}
		MAX-ACCESS  read-only
		STATUS      current
		DESCRIPTION
			"The loading status of this ATS.
			 (0)=normal,loading is not in ecess of over load threshold. (1)=over load alarm is triggerd."
		::= { atsEntry 12 }
		--tb_ATS.ATS_OverLoadStage
	atsConnection OBJECT-TYPE
		SYNTAX      INTEGER {
				   disconnected      (0),
				   connected    (1)
				}
		MAX-ACCESS  read-only
		STATUS      current
		DESCRIPTION
			"The connection status of this ATS.
			 (0)=disconnected (1)=connected."
		::= { atsEntry 13 }
		--tb_ATS.ATS_Connection
		
	--
	--	atsTraps
	--
	atsTraps	OBJECT IDENTIFIER	::= { atsGroup 2 }

	atsOverLoadEventTriggered		NOTIFICATION-TYPE
		OBJECTS {
			atsIndex, atsName, atsLocation, atsOutputFromFeed, atsTotalLoadAmp, atsOverLoadThreshold, atsOverLoadStage
		}
		STATUS      current
		DESCRIPTION
			"The over load alarm of this ATS is triggered.
			 The trap sends out within 10 seconds in cycle until the total current reading returns below the atsOverLoadThreshold."
		::= { atsTraps 1 }
	atsOverLoadEventCleared		NOTIFICATION-TYPE
		OBJECTS {
			atsIndex, atsName, atsLocation, atsOutputFromFeed, atsTotalLoadAmp, atsOverLoadThreshold,atsOverLoadStage
		}
		STATUS      current
		DESCRIPTION
			"The over load alarm of this ATS is cleared.
			 The trap sends out once only when the over load alarm is cleared."
		::= { atsTraps 2 }
	atsPrimaryFeedOfflineEventTriggered		NOTIFICATION-TYPE
		OBJECTS {
			atsIndex, atsName, atsLocation, atsOutputFromFeed, atsFeedPrimaryStatus
		}
		STATUS      current
		DESCRIPTION
			"The Primary feed status of this ATS changed to offline is triggered.
			 The trap sends out within 10 seconds in cycle until the feed status is recovered(online)."
		::= { atsTraps 3 }
	atsPrimaryFeedOfflineEventCleared		NOTIFICATION-TYPE
		OBJECTS {
			atsIndex, atsName, atsLocation, atsOutputFromFeed, atsFeedPrimaryStatus
		}
		STATUS      current
		DESCRIPTION
			"The Primary feed status of this ATS is recovered(online).
			 The trap sends out once only when the feed status is recovered(online)."
		::= { atsTraps 4 }

	atsSecondaryFeedOfflineEventTriggered		NOTIFICATION-TYPE
		OBJECTS {
			atsIndex, atsName, atsLocation, atsOutputFromFeed, atsFeedSecondaryStatus
		}
		STATUS      current
		DESCRIPTION
			"The Secondary feed status of this ATS changed to offline is triggered.
			 The trap sends out within 10 seconds in cycle until the feed status is recovered(online)."
		::= { atsTraps 5 }

	atsSecondaryFeedOfflineEventCleared		NOTIFICATION-TYPE
		OBJECTS {
			atsIndex, atsName, atsLocation, atsOutputFromFeed, atsFeedSecondaryStatus
		}
		STATUS      current
		DESCRIPTION
			"The Secondary feed status of this ATS is recovered(online).
			 The trap sends out once only when the feed status is recovered(online)."
		::= { atsTraps 6 }

	atsInputSwitchEventTriggered		NOTIFICATION-TYPE
		OBJECTS {
			atsIndex, atsName, atsLocation, atsOutputFromFeed, atsInputSwitch
		}
		STATUS      current
		DESCRIPTION
			"The input switch is changed via local front button or remote web UI.
			 The trap sends out once only when the input switch is changed."
		::= { atsTraps 7 }

	atsOnFailAutoSwitchFeedEventTriggered		NOTIFICATION-TYPE
		OBJECTS {
			atsIndex, atsName, atsLocation, atsOutputFromFeed, atsInputSwitch
		}
		STATUS      current
		DESCRIPTION
			"The ouput feed is switched to the other online feed when the current feed status is offline..
			 The trap sends out once only when the input switch is changed."
		::= { atsTraps 8 }

	atsConnectionLost		NOTIFICATION-TYPE
		OBJECTS {
			atsIndex, atsName, atsLocation
		}
		STATUS      current
		DESCRIPTION
			"The ATS is disconnected
			  The trap sends out within 10 seconds in cycle until the connection is recovered."
		::= { atsTraps 9 }

	atsConnectionRecovered		NOTIFICATION-TYPE
		OBJECTS {
			atsIndex, atsName, atsLocation
		}
		STATUS      current
		DESCRIPTION
			"The ATS is re-connected
			  The trap sends out once only when the connection is recovered."
		::= { atsTraps 10 }		
END
